--
P21451-N1-T1-MIB DEFINITIONS ::= BEGIN
 
IMPORTS
    enterprises
        FROM RFC1155-SMI
    Integer32,OBJECT-TYPE
        FROM SNMPv2-SMI
    DisplayString, TEXTUAL-CONVENTION
        FROM SNMPv2-TC;
 
 

--enterprises  1.3.6.1.4
ncap  OBJECT IDENTIFIER ::= { enterprises 21451 }
 
ncapone OBJECT IDENTIFIER ::= {ncap  1}

timone  OBJECT IDENTIFIER ::= {ncapone  1}
timdescrption  OBJECT IDENTIFIER ::={timone 0}

sensors  OBJECT IDENTIFIER ::= {timone  1}
timcpu OBJECT IDENTIFIER ::={timdescrption 1}


slope OBJECT IDENTIFIER ::={sensors 1}

SlopeSwitch OBJECT-TYPE
SYNTAX      DisplayString
MAX-ACCESS  read-write
STATUS      current
DESCRIPTION
"Slope Switch"
::= {slope 1}

SlopeOut OBJECT-TYPE
SYNTAX      DisplayString
MAX-ACCESS  read-only
STATUS      current
DESCRIPTION
"Slpoe Out"
::= {slope 2}

temperature OBJECT IDENTIFIER ::={sensors 2}

TemperatureSwitch OBJECT-TYPE
SYNTAX      DisplayString
MAX-ACCESS  read-write
STATUS      current
DESCRIPTION
"TemperatureSwitch"
::= {temperature 1}

TemperatureOut OBJECT-TYPE
SYNTAX      DisplayString
MAX-ACCESS  read-only
STATUS      current
DESCRIPTION 
"TemperatureOut"
::= {temperature 2}

pressure OBJECT IDENTIFIER ::={sensors 3}

PressureSwitch OBJECT-TYPE
SYNTAX      DisplayString
MAX-ACCESS  read-write
STATUS      current
DESCRIPTION
"PressureSwitch"
::= {pressure 1}

PressureOut OBJECT-TYPE
SYNTAX      DisplayString
MAX-ACCESS  read-only
STATUS      current
DESCRIPTION
"PressureOut"
::= {pressure 2}

light OBJECT IDENTIFIER ::={sensors 4}

LightSwitch OBJECT-TYPE
SYNTAX      DisplayString
MAX-ACCESS  read-write
STATUS      current
DESCRIPTION 
"light switch"
::= {light 1}

LightIn OBJECT-TYPE
SYNTAX      DisplayString
MAX-ACCESS  read-write
STATUS      current
DESCRIPTION
"PressureOut"
::= {light 2}


lcd OBJECT IDENTIFIER ::={sensors 5}

LCDdisplay OBJECT-TYPE
SYNTAX      DisplayString
MAX-ACCESS  read-write
STATUS      current
DESCRIPTION
"LCD dispaly"
::= {lcd 1}

LCDIn OBJECT-TYPE
SYNTAX      DisplayString
MAX-ACCESS  read-write
STATUS      current
DESCRIPTION
"PressureOut"
::= {lcd 2}

buzzer OBJECT IDENTIFIER ::={sensors 6}

BuzzerSwitch OBJECT-TYPE
SYNTAX      DisplayString
MAX-ACCESS  read-write
STATUS      current
DESCRIPTION
"Buzzer Switch"
::= {buzzer 1}

BuzzerIn OBJECT-TYPE
SYNTAX      DisplayString
MAX-ACCESS  read-write
STATUS      current
DESCRIPTION
"Buzzer Output"
::= {buzzer 2}

anaone OBJECT IDENTIFIER ::={sensors 7}

AnaOneSwitch OBJECT-TYPE
SYNTAX      DisplayString
MAX-ACCESS  read-write
STATUS      current
DESCRIPTION
"Analogue One Switch"
::= {anaone 1}

AnaOneOut OBJECT-TYPE
SYNTAX      DisplayString
MAX-ACCESS  read-only
STATUS      current
DESCRIPTION
"Analogue One Out"
::= {anaone 2}


anatwo OBJECT IDENTIFIER ::={sensors 8}

AnaTwoSwitch OBJECT-TYPE
SYNTAX      DisplayString
MAX-ACCESS  read-write
STATUS      current
DESCRIPTION
"Analogue Two Switch"
::= {anatwo 1}

anatwoout OBJECT-TYPE
SYNTAX      DisplayString
MAX-ACCESS  read-only
STATUS      current
DESCRIPTION
"Analogue Two Out"
::= {anatwo 2}

anathree OBJECT IDENTIFIER ::={sensors 9}

AnThreeSwitch OBJECT-TYPE
SYNTAX      DisplayString
MAX-ACCESS  read-write
STATUS      current
DESCRIPTION
"Analogue Three Switch"
::= {anathree 1}

AnaThreeOut OBJECT-TYPE
SYNTAX      DisplayString
MAX-ACCESS  read-only
STATUS      current
DESCRIPTION
"Analogue Three Out"
::= {anathree 2}

anafour OBJECT IDENTIFIER ::={sensors 10}

AnaFourSwitch OBJECT-TYPE
SYNTAX      DisplayString
MAX-ACCESS  read-write
STATUS      current
DESCRIPTION
"Analogue Four Switch"
::= {anafour 1}

AnaFourOut OBJECT-TYPE
SYNTAX      DisplayString
MAX-ACCESS  read-only
STATUS      current
DESCRIPTION
"Analogue Four Out"
::= {anafour 2}


digone OBJECT IDENTIFIER ::={sensors 11}

DigOneSwitch OBJECT-TYPE
SYNTAX      DisplayString
MAX-ACCESS  read-write
STATUS      current
DESCRIPTION
"Digital One Switch"
::= {digone 1}

DigOneOut OBJECT-TYPE
SYNTAX      DisplayString
MAX-ACCESS  read-only
STATUS      current
DESCRIPTION
"Digital One Out"
::= {digone 2}

digtwo OBJECT IDENTIFIER ::={sensors 12}

DigTwoSwitch OBJECT-TYPE
SYNTAX      DisplayString
MAX-ACCESS  read-write
STATUS      current
DESCRIPTION
"Digital Two Switch"
::= {digtwo 1}

DigTwoOut OBJECT-TYPE
SYNTAX      DisplayString
MAX-ACCESS  read-only
STATUS      current
DESCRIPTION
"Digital Two Out"
::= {digtwo 2}

digthree OBJECT IDENTIFIER ::={sensors 13}

DigThreeSwitch OBJECT-TYPE
SYNTAX      DisplayString
MAX-ACCESS  read-write
STATUS      current
DESCRIPTION
"Digital Three Switch"
::= {digthree 1}

DigThreeOut OBJECT-TYPE
SYNTAX      DisplayString
MAX-ACCESS  read-only
STATUS      current
DESCRIPTION
"Digital Three Out"
::= {digthree 2}





MainFrequency OBJECT-TYPE
SYNTAX      DisplayString
MAX-ACCESS  read-only
STATUS      current
DESCRIPTION
"the main frequency of TIM CPU"
::= {timcpu 1}

Temperature OBJECT-TYPE
SYNTAX      DisplayString
MAX-ACCESS  read-only
STATUS      current
DESCRIPTION
"the temperature of TIM CPU"
::= {timcpu 2}

Usage OBJECT-TYPE
SYNTAX      DisplayString
MAX-ACCESS  read-only
STATUS      current
DESCRIPTION
"the usage of TIM CPU"
::= {timcpu 3}


END
