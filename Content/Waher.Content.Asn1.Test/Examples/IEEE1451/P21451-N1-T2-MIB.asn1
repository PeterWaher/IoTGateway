--
P21451-N1-T2-MIB DEFINITIONS ::= BEGIN
 
IMPORTS
    enterprises
        FROM RFC1155-SMI
    Integer32,OBJECT-TYPE
        FROM SNMPv2-SMI
    DisplayString, TEXTUAL-CONVENTION
        FROM SNMPv2-TC;
 
 

--enterprises  1.3.6.1.4
ncap  OBJECT IDENTIFIER ::= { enterprises 21451 }
 
ncapone OBJECT IDENTIFIER ::= {ncap  1}

timtwo  OBJECT IDENTIFIER ::= {ncapone  2}
timdescrptiontwo  OBJECT IDENTIFIER ::={timtwo 0}

sensorstwo  OBJECT IDENTIFIER ::= {timtwo  1}
timcpu2 OBJECT IDENTIFIER ::={timdescrptiontwo 1}


slope2 OBJECT IDENTIFIER ::={sensorstwo 1}

SlopeSwitch2 OBJECT-TYPE
SYNTAX      DisplayString
MAX-ACCESS  read-write
STATUS      current
DESCRIPTION
"Slope Switch"
::= {slope2 1}

SlopeOut2 OBJECT-TYPE
SYNTAX      DisplayString
MAX-ACCESS  read-only
STATUS      current
DESCRIPTION
"Slpoe Out"
::= {slope2 2}

temperature2 OBJECT IDENTIFIER ::={sensorstwo 2}

TemperatureSwitch OBJECT-TYPE
SYNTAX      DisplayString
MAX-ACCESS  read-write
STATUS      current
DESCRIPTION
"TemperatureSwitch"
::= {temperature2 1}

TemperatureOut OBJECT-TYPE
SYNTAX      DisplayString
MAX-ACCESS  read-only
STATUS      current
DESCRIPTION 
"TemperatureOut"
::= {temperature2 2}

pressure2 OBJECT IDENTIFIER ::={sensorstwo 3}

PressureSwitch2 OBJECT-TYPE
SYNTAX      DisplayString
MAX-ACCESS  read-write
STATUS      current
DESCRIPTION
"PressureSwitch"
::= {pressure2 1}

PressureOut2 OBJECT-TYPE
SYNTAX      DisplayString
MAX-ACCESS  read-only
STATUS      current
DESCRIPTION
"PressureOut"
::= {pressure2 2}

light2 OBJECT IDENTIFIER ::={sensorstwo 4}

LightSwitch2 OBJECT-TYPE
SYNTAX      DisplayString
MAX-ACCESS  read-write
STATUS      current
DESCRIPTION 
"light switch"
::= {light2 1}

LightIn2 OBJECT-TYPE
SYNTAX      DisplayString
MAX-ACCESS  read-write
STATUS      current
DESCRIPTION
"PressureOut"
::= {light2 2}


lcd2 OBJECT IDENTIFIER ::={sensorstwo 5}

lcddisplay2 OBJECT-TYPE
SYNTAX      DisplayString
MAX-ACCESS  read-write
STATUS      current
DESCRIPTION
"LCD dispaly"
::= {lcd2 1}

lcdin2 OBJECT-TYPE
SYNTAX      DisplayString
MAX-ACCESS  read-write
STATUS      current
DESCRIPTION
"PressureOut"
::= {lcd2 2}

buzzer2 OBJECT IDENTIFIER ::={sensorstwo 6}
BuzzerSwitch2 OBJECT-TYPE
SYNTAX      DisplayString
MAX-ACCESS  read-write
STATUS      current
DESCRIPTION
"Buzzer2 Switch"
::= {buzzer2 1}

BuzzerIn2 OBJECT-TYPE
SYNTAX      DisplayString
MAX-ACCESS  read-write
STATUS      current
DESCRIPTION
"Buzzer Output"
::= {buzzer2 2}

anaone2 OBJECT IDENTIFIER ::={sensorstwo 7}
AnaOneSwitch2 OBJECT-TYPE
SYNTAX      DisplayString
MAX-ACCESS  read-write
STATUS      current
DESCRIPTION
"Analogue One Switch"
::= {anaone2 1}

AnaOneOut2 OBJECT-TYPE
SYNTAX      DisplayString
MAX-ACCESS  read-only
STATUS      current
DESCRIPTION
"Analogue One Out"
::= {anaone2 2}


anatwo2 OBJECT IDENTIFIER ::={sensorstwo 8}
AnaTwoSwitch2 OBJECT-TYPE
SYNTAX      DisplayString
MAX-ACCESS  read-write
STATUS      current
DESCRIPTION
"Analogue Two Switch"
::= {anatwo2 1}

AnaTwoOut2 OBJECT-TYPE
SYNTAX      DisplayString
MAX-ACCESS  read-only
STATUS      current
DESCRIPTION
"Analogue Two Out"
::= {anatwo2 2}

anathree2 OBJECT IDENTIFIER ::={sensorstwo 9}
AnThreeSwitch2 OBJECT-TYPE
SYNTAX      DisplayString
MAX-ACCESS  read-write
STATUS      current
DESCRIPTION
"Analogue Three Switch"
::= {anathree2 1}

AnaThreeOut2 OBJECT-TYPE
SYNTAX      DisplayString
MAX-ACCESS  read-only
STATUS      current
DESCRIPTION
"Analogue Three Out"
::= {anathree2 2}

anafour2 OBJECT IDENTIFIER ::={sensorstwo 10}
AnaFourSwitch2 OBJECT-TYPE
SYNTAX      DisplayString
MAX-ACCESS  read-write
STATUS      current
DESCRIPTION
"Analogue Four Switch"
::= {anafour2 1}

anafourout2 OBJECT-TYPE
SYNTAX      DisplayString
MAX-ACCESS  read-only
STATUS      current
DESCRIPTION
"Analogue Four Out"
::= {anafour2 2}


digone2 OBJECT IDENTIFIER ::={sensorstwo 11}
DigOneSwitch2 OBJECT-TYPE
SYNTAX      DisplayString
MAX-ACCESS  read-write
STATUS      current
DESCRIPTION
"Digital One Switch"
::= {digone2 1}

digoneout2 OBJECT-TYPE
SYNTAX      DisplayString
MAX-ACCESS  read-only
STATUS      current
DESCRIPTION
"Digital One Out"
::= {digone2 2}

digtwo2 OBJECT IDENTIFIER ::={sensorstwo 12}
DigTwoSwitch2 OBJECT-TYPE
SYNTAX      DisplayString
MAX-ACCESS  read-write
STATUS      current
DESCRIPTION
"Digital Two Switch"
::= {digtwo2 1}

DigTwoOut2 OBJECT-TYPE
SYNTAX      DisplayString
MAX-ACCESS  read-only
STATUS      current
DESCRIPTION
"Digital Two Out"
::= {digtwo2 2}

digthree2 OBJECT IDENTIFIER ::={sensorstwo 13}
DigThreeSwitch2 OBJECT-TYPE
SYNTAX      DisplayString
MAX-ACCESS  read-write
STATUS      current
DESCRIPTION
"Digital Three Switch"
::= {digthree2 1}

DigThreeOut2 OBJECT-TYPE
SYNTAX      DisplayString
MAX-ACCESS  read-only
STATUS      current
DESCRIPTION
"Digital Three Out"
::= {digthree2 2}





MainFrequency2 OBJECT-TYPE
SYNTAX      DisplayString
MAX-ACCESS  read-only
STATUS      current
DESCRIPTION
"the main frequency of TIM CPU"
::= {timcpu2 1}

Temperature2 OBJECT-TYPE
SYNTAX      DisplayString
MAX-ACCESS  read-only
STATUS      current
DESCRIPTION
"the temperature of TIM CPU"
::= {timcpu2 2}

Usage2 OBJECT-TYPE
SYNTAX      DisplayString
MAX-ACCESS  read-only
STATUS      current
DESCRIPTION
"the usage of TIM CPU"
::= {timcpu2 3}


END
