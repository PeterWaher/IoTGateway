--
P21451-N1-T3-MIB DEFINITIONS ::= BEGIN
 
IMPORTS
    enterprises
        FROM RFC1155-SMI
    Integer32,OBJECT-TYPE
        FROM SNMPv2-SMI
    DisplayString, TEXTUAL-CONVENTION
        FROM SNMPv2-TC;
 
 

--enterprises  1.3.6.1.4
ncap  OBJECT IDENTIFIER ::= { enterprises 21451 }
 
ncapone OBJECT IDENTIFIER ::= {ncap  1}

timthree  OBJECT IDENTIFIER ::= {ncapone  3}
timdescrptionthree  OBJECT IDENTIFIER ::={timthree 0}

sensorsthree  OBJECT IDENTIFIER ::= {timthree  1}
timcpu3 OBJECT IDENTIFIER ::={timdescrptionthree 1}


slope3 OBJECT IDENTIFIER ::={sensorsthree 1}

SlopeSwitch3 OBJECT-TYPE
SYNTAX      DisplayString
MAX-ACCESS  read-write
STATUS      current
DESCRIPTION
"Slope Switch"
::= {slope3 1}

SlopeOut3 OBJECT-TYPE
SYNTAX      DisplayString
MAX-ACCESS  read-only
STATUS      current
DESCRIPTION
"Slpoe Out"
::= {slope3 2}

temperature3 OBJECT IDENTIFIER ::={sensorsthree 2}

TemperatureSwitch OBJECT-TYPE
SYNTAX      DisplayString
MAX-ACCESS  read-write
STATUS      current
DESCRIPTION
"TemperatureSwitch"
::= {temperature3 1}

TemperatureOut3 OBJECT-TYPE
SYNTAX      DisplayString
MAX-ACCESS  read-only
STATUS      current
DESCRIPTION 
"TemperatureOut"
::= {temperature3 2}

pressure3 OBJECT IDENTIFIER ::={sensorsthree 3}

PressureSwitch3 OBJECT-TYPE
SYNTAX      DisplayString
MAX-ACCESS  read-write
STATUS      current
DESCRIPTION
"PressureSwitch"
::= {pressure3 1}

PressureOut3 OBJECT-TYPE
SYNTAX      DisplayString
MAX-ACCESS  read-only
STATUS      current
DESCRIPTION
"PressureOut"
::= {pressure3 2}

light3 OBJECT IDENTIFIER ::={sensorsthree 4}

LightSwitch3 OBJECT-TYPE
SYNTAX      DisplayString
MAX-ACCESS  read-write
STATUS      current
DESCRIPTION 
"light switch"
::= {light3 1}

LightIn3 OBJECT-TYPE
SYNTAX      DisplayString
MAX-ACCESS  read-write
STATUS      current
DESCRIPTION
"PressureOut"
::= {light3 2}


lcd3 OBJECT IDENTIFIER ::={sensorsthree 5}

LCDdisplay3 OBJECT-TYPE
SYNTAX      DisplayString
MAX-ACCESS  read-write
STATUS      current
DESCRIPTION
"LCD dispaly"
::= {lcd3 1}

LCDIn3 OBJECT-TYPE
SYNTAX      DisplayString
MAX-ACCESS  read-write
STATUS      current
DESCRIPTION
"PressureOut"
::= {lcd3 2}

buzzer3 OBJECT IDENTIFIER ::={sensorsthree 6}
BuzzerSwitch3 OBJECT-TYPE
SYNTAX      DisplayString
MAX-ACCESS  read-write
STATUS      current
DESCRIPTION
"Buzzer3 Switch"
::= {buzzer3 1}

BuzzerIn3 OBJECT-TYPE
SYNTAX      DisplayString
MAX-ACCESS  read-write
STATUS      current
DESCRIPTION
"Buzzer Output"
::= {buzzer3 2}

anaone3 OBJECT IDENTIFIER ::={sensorsthree 7}
AnaOneSwitch3 OBJECT-TYPE
SYNTAX      DisplayString
MAX-ACCESS  read-write
STATUS      current
DESCRIPTION
"Analogue One Switch"
::= {anaone3 1}

AnaOneOut3 OBJECT-TYPE
SYNTAX      DisplayString
MAX-ACCESS  read-only
STATUS      current
DESCRIPTION
"Analogue One Out"
::= {anaone3 2}


anatwo3 OBJECT IDENTIFIER ::={sensorsthree 8}
AnaTwoSwitch3 OBJECT-TYPE
SYNTAX      DisplayString
MAX-ACCESS  read-write
STATUS      current
DESCRIPTION
"Analogue Two Switch"
::= {anatwo3 1}

AnaTwoOut3 OBJECT-TYPE
SYNTAX      DisplayString
MAX-ACCESS  read-only
STATUS      current
DESCRIPTION
"Analogue Two Out"
::= {anatwo3 2}

anathree3 OBJECT IDENTIFIER ::={sensorsthree 9}
AnThreeSwitch3 OBJECT-TYPE
SYNTAX      DisplayString
MAX-ACCESS  read-write
STATUS      current
DESCRIPTION
"Analogue Three Switch"
::= {anathree3 1}

AnaThreeOut3 OBJECT-TYPE
SYNTAX      DisplayString
MAX-ACCESS  read-only
STATUS      current
DESCRIPTION
"Analogue Three Out"
::= {anathree3 2}

anafour3 OBJECT IDENTIFIER ::={sensorsthree 10}
AnaFourSwitch3 OBJECT-TYPE
SYNTAX      DisplayString
MAX-ACCESS  read-write
STATUS      current
DESCRIPTION
"Analogue Four Switch"
::= {anafour3 1}

AnaFourOut3 OBJECT-TYPE
SYNTAX      DisplayString
MAX-ACCESS  read-only
STATUS      current
DESCRIPTION
"Analogue Four Out"
::= {anafour3 2}


digone3 OBJECT IDENTIFIER ::={sensorsthree 11}
DigOneSwitch3 OBJECT-TYPE
SYNTAX      DisplayString
MAX-ACCESS  read-write
STATUS      current
DESCRIPTION
"Digital One Switch"
::= {digone3 1}

DigOneOut3 OBJECT-TYPE
SYNTAX      DisplayString
MAX-ACCESS  read-only
STATUS      current
DESCRIPTION
"Digital One Out"
::= {digone3 2}

digtwo3 OBJECT IDENTIFIER ::={sensorsthree 12}
DigTwoSwitch3 OBJECT-TYPE
SYNTAX      DisplayString
MAX-ACCESS  read-write
STATUS      current
DESCRIPTION
"Digital Two Switch"
::= {digtwo3 1}

DigTwoOut3 OBJECT-TYPE
SYNTAX      DisplayString
MAX-ACCESS  read-only
STATUS      current
DESCRIPTION
"Digital Two Out"
::= {digtwo3 2}

digthree3 OBJECT IDENTIFIER ::={sensorsthree 13}
DigThreeSwitch3 OBJECT-TYPE
SYNTAX      DisplayString
MAX-ACCESS  read-write
STATUS      current
DESCRIPTION
"Digital Three Switch"
::= {digthree3 1}

DigThreeOut3 OBJECT-TYPE
SYNTAX      DisplayString
MAX-ACCESS  read-only
STATUS      current
DESCRIPTION
"Digital Three Out"
::= {digthree3 2}





MainFrequency3 OBJECT-TYPE
SYNTAX      DisplayString
MAX-ACCESS  read-only
STATUS      current
DESCRIPTION
"the main frequency of TIM CPU"
::= {timcpu3 1}

Temperature3 OBJECT-TYPE
SYNTAX      DisplayString
MAX-ACCESS  read-only
STATUS      current
DESCRIPTION
"the temperature of TIM CPU"
::= {timcpu3 2}

Usage3 OBJECT-TYPE
SYNTAX      DisplayString
MAX-ACCESS  read-only
STATUS      current
DESCRIPTION
"the usage of TIM CPU"
::= {timcpu3 3}


END
